EQUALIZER-MIB DEFINITIONS ::= BEGIN

IMPORTS
    OBJECT-TYPE, MODULE-IDENTITY, enterprises,
    Integer32, OBJECT-IDENTITY
    	FROM SNMPv2-SMI
    OBJECT-GROUP, MODULE-COMPLIANCE
        FROM SNMPv2-CONF
    DisplayString
    	FROM SNMPv2-TC;

equalizer MODULE-IDENTITY
    LAST-UPDATED "201708070000Z"
    ORGANIZATION "CM Comandos Lineares"
    CONTACT-INFO "assistencia@cmcomandos.com.br"
    DESCRIPTION
       "Modulo de leitura do produto Equalizer."

    REVISION "201708070000Z"
    DESCRIPTION "Revisao inicial."

    ::= { project 1 }

-- We are hosted under The IMS Company OID.
imsco			OBJECT IDENTIFIER ::= { enterprises 39178 }
project			OBJECT IDENTIFIER ::= { imsco 100 }

---settings object, counpounded by parameters, modulo, usuarios and redeseguranca tables

settingsObject OBJECT-IDENTITY
    STATUS          current
    DESCRIPTION
        "Main settings object for equalizer"
    ::= { equalizer 1 }

parametersEntry OBJECT-IDENTITY
    STATUS  current
    DESCRIPTION
            "Parameters table"
    ::= { settingsObject 1 }

avgLast OBJECT-TYPE
    SYNTAX      DisplayString
    MAX-ACCESS  read-only
    STATUS      current
    DESCRIPTION
            "Description"
    ::= { parametersEntry 1 }

dutyMin OBJECT-TYPE
    SYNTAX      DisplayString
    MAX-ACCESS  read-only
    STATUS      current
    DESCRIPTION
            "Description"
    ::= { parametersEntry 2 }

dutyMax OBJECT-TYPE
    SYNTAX      DisplayString
    MAX-ACCESS  read-only
    STATUS      current
    DESCRIPTION
            "Description"
    ::= { parametersEntry 3 }

cteIndex OBJECT-TYPE
    SYNTAX      DisplayString
    MAX-ACCESS  read-only
    STATUS      current
    DESCRIPTION
            "Description"
    ::= { parametersEntry 4 }

delay OBJECT-TYPE
    SYNTAX      DisplayString
    MAX-ACCESS  read-only
    STATUS      current
    DESCRIPTION
            "Description"
    ::= { parametersEntry 5 }

numCyclesVarRead OBJECT-TYPE
    SYNTAX      DisplayString
    MAX-ACCESS  read-only
    STATUS      current
    DESCRIPTION
            "Description"
    ::= { parametersEntry 6 }

busVoltage OBJECT-TYPE
    SYNTAX      DisplayString
    MAX-ACCESS  read-only
    STATUS      current
    DESCRIPTION
            "Description"
    ::= { parametersEntry 7 }

saveLogTime OBJECT-TYPE
    SYNTAX      DisplayString
    MAX-ACCESS  read-only
    STATUS      current
    DESCRIPTION
            "Description"
    ::= { parametersEntry 8 }

diskCapacity OBJECT-TYPE
    SYNTAX      DisplayString
    MAX-ACCESS  read-only
    STATUS      current
    DESCRIPTION
            "Description"
    ::= { parametersEntry 9 }

param1 OBJECT-TYPE
    SYNTAX      DisplayString
    MAX-ACCESS  read-only
    STATUS      current
    DESCRIPTION
            "Description"
    ::= { parametersEntry 10 }

param2 OBJECT-TYPE
    SYNTAX      DisplayString
    MAX-ACCESS  read-only
    STATUS      current
    DESCRIPTION
            "Description"
    ::= { parametersEntry 11 }

param3 OBJECT-TYPE
    SYNTAX      DisplayString
    MAX-ACCESS  read-only
    STATUS      current
    DESCRIPTION
            "Description"
    ::= { parametersEntry 12 }

param4 OBJECT-TYPE
    SYNTAX      DisplayString
    MAX-ACCESS  read-only
    STATUS      current
    DESCRIPTION
            "Description"
    ::= { parametersEntry 13 }

param5 OBJECT-TYPE
    SYNTAX      DisplayString
    MAX-ACCESS  read-only
    STATUS      current
    DESCRIPTION
            "Description"
    ::= { parametersEntry 14 }

param6 OBJECT-TYPE
    SYNTAX      DisplayString
    MAX-ACCESS  read-only
    STATUS      current
    DESCRIPTION
            "Description"
    ::= { parametersEntry 15 }

param7 OBJECT-TYPE
    SYNTAX      DisplayString
    MAX-ACCESS  read-only
    STATUS      current
    DESCRIPTION
            "Description"
    ::= { parametersEntry 16 }

param8 OBJECT-TYPE
    SYNTAX      DisplayString
    MAX-ACCESS  read-only
    STATUS      current
    DESCRIPTION
            "Description"
    ::= { parametersEntry 17 }

param9 OBJECT-TYPE
    SYNTAX      DisplayString
    MAX-ACCESS  read-only
    STATUS      current
    DESCRIPTION
            "Description"
    ::= { parametersEntry 18 }

param10 OBJECT-TYPE
    SYNTAX      DisplayString
    MAX-ACCESS  read-only
    STATUS      current
    DESCRIPTION
            "Description"
    ::= { parametersEntry 19 }

moduloObjectEntry OBJECT-IDENTITY
    STATUS  current
    DESCRIPTION
            "Modulo table"
    ::= { settingsObject 2 }

descricao OBJECT-TYPE
    SYNTAX      DisplayString
    MAX-ACCESS  read-only
    STATUS      current
    DESCRIPTION
            "Description"
    ::= { moduloObjectEntry 1 }

tensaoNominal OBJECT-TYPE
    SYNTAX      DisplayString
    MAX-ACCESS  read-only
    STATUS      current
    DESCRIPTION
            "Description"
    ::= { moduloObjectEntry 2 }

capacidadeNominal OBJECT-TYPE
    SYNTAX      Integer32
    MAX-ACCESS  read-only
    STATUS      current
    DESCRIPTION
            "Description"
    ::= { moduloObjectEntry 3 }

nStrings OBJECT-TYPE
    SYNTAX      Integer32
    MAX-ACCESS  read-only
    STATUS      current
    DESCRIPTION
            "Description"
    ::= { moduloObjectEntry 4 }

nBateriasPorStrings OBJECT-TYPE
    SYNTAX      Integer32
    MAX-ACCESS  read-only
    STATUS      current
    DESCRIPTION
            "Description"
    ::= { moduloObjectEntry 5 }

contato OBJECT-TYPE
    SYNTAX      DisplayString
    MAX-ACCESS  read-only
    STATUS      current
    DESCRIPTION
            "Description"
    ::= { moduloObjectEntry 6 }

localizacao OBJECT-TYPE
    SYNTAX      DisplayString
    MAX-ACCESS  read-only
    STATUS      current
    DESCRIPTION
            "Description"
    ::= { moduloObjectEntry 7 }

fabricante OBJECT-TYPE
    SYNTAX      DisplayString
    MAX-ACCESS  read-only
    STATUS      current
    DESCRIPTION
            "Description"
    ::= { moduloObjectEntry 8 }

tipo OBJECT-TYPE
    SYNTAX      DisplayString
    MAX-ACCESS  read-only
    STATUS      current
    DESCRIPTION
            "Description"
    ::= { moduloObjectEntry 9 }

dataInstalacao OBJECT-TYPE
    SYNTAX      DisplayString
    MAX-ACCESS  read-only
    STATUS      current
    DESCRIPTION
            "Description"
    ::= { moduloObjectEntry 10 }

confAlarmeId OBJECT-TYPE
    SYNTAX      Integer32
    MAX-ACCESS  read-only
    STATUS      current
    DESCRIPTION
            "Description"
    ::= { moduloObjectEntry 11 }

usuariosObjectEntry OBJECT-IDENTITY
    STATUS  current
    DESCRIPTION
            "Usuarios table"
    ::= { settingsObject 3 }

nome OBJECT-TYPE
    SYNTAX      DisplayString
    MAX-ACCESS  read-only
    STATUS      current
    DESCRIPTION
            "Description"
    ::= { usuariosObjectEntry 1 }

sobreNome OBJECT-TYPE
    SYNTAX      DisplayString
    MAX-ACCESS  read-only
    STATUS      current
    DESCRIPTION
            "Description"
    ::= { usuariosObjectEntry 2 }

telefone OBJECT-TYPE
    SYNTAX      DisplayString
    MAX-ACCESS  read-only
    STATUS      current
    DESCRIPTION
            "Description"
    ::= { usuariosObjectEntry 3 }

email OBJECT-TYPE
    SYNTAX      DisplayString
    MAX-ACCESS  read-only
    STATUS      current
    DESCRIPTION
            "Description"
    ::= { usuariosObjectEntry 4 }

senha OBJECT-TYPE
    SYNTAX      DisplayString
    MAX-ACCESS  read-only
    STATUS      current
    DESCRIPTION
            "Description"
    ::= { usuariosObjectEntry 5 }

acesso OBJECT-TYPE
    SYNTAX      DisplayString
    MAX-ACCESS  read-only
    STATUS      current
    DESCRIPTION
            "Description"
    ::= { usuariosObjectEntry 6 }

redeSegurancaObjectEntry OBJECT-IDENTITY
    STATUS  current
    DESCRIPTION
            "RedeSeguranca table"
    ::= { settingsObject 4 }

mac OBJECT-TYPE
    SYNTAX      DisplayString
    MAX-ACCESS  read-only
    STATUS      current
    DESCRIPTION
            "Description"
    ::= { redeSegurancaObjectEntry 1 }

velocidadePlacaRede OBJECT-TYPE
    SYNTAX      DisplayString
    MAX-ACCESS  read-only
    STATUS      current
    DESCRIPTION
            "Description"
    ::= { redeSegurancaObjectEntry 2 }

localAddress OBJECT-TYPE
    SYNTAX      DisplayString
    MAX-ACCESS  read-only
    STATUS      current
    DESCRIPTION
            "Description"
    ::= { redeSegurancaObjectEntry 3 }

gateway OBJECT-TYPE
    SYNTAX      DisplayString
    MAX-ACCESS  read-only
    STATUS      current
    DESCRIPTION
            "Description"
    ::= { redeSegurancaObjectEntry 4 }

mascara OBJECT-TYPE
    SYNTAX      DisplayString
    MAX-ACCESS  read-only
    STATUS      current
    DESCRIPTION
            "Description"
    ::= { redeSegurancaObjectEntry 5 }

servidorDNS OBJECT-TYPE
    SYNTAX      DisplayString
    MAX-ACCESS  read-only
    STATUS      current
    DESCRIPTION
            "Description"
    ::= { redeSegurancaObjectEntry 6 }

nomeDoSistema OBJECT-TYPE
    SYNTAX      DisplayString
    MAX-ACCESS  read-only
    STATUS      current
    DESCRIPTION
            "Description"
    ::= { redeSegurancaObjectEntry 7 }

localDoSistema OBJECT-TYPE
    SYNTAX      DisplayString
    MAX-ACCESS  read-only
    STATUS      current
    DESCRIPTION
            "Description"
    ::= { redeSegurancaObjectEntry 8 }

contatoDoSistema OBJECT-TYPE
    SYNTAX      DisplayString
    MAX-ACCESS  read-only
    STATUS      current
    DESCRIPTION
            "Description"
    ::= { redeSegurancaObjectEntry 9 }

httpPort OBJECT-TYPE
    SYNTAX      Integer32
    MAX-ACCESS  read-only
    STATUS      current
    DESCRIPTION
            "Description"
    ::= { redeSegurancaObjectEntry 10 }

useHttps OBJECT-TYPE
    SYNTAX      Integer32
    MAX-ACCESS  read-only
    STATUS      current
    DESCRIPTION
            "Description"
    ::= { redeSegurancaObjectEntry 11 }

httpsPort OBJECT-TYPE
    SYNTAX      Integer32
    MAX-ACCESS  read-only
    STATUS      current
    DESCRIPTION
            "Description"
    ::= { redeSegurancaObjectEntry 12 }

httpTempoDeAtualizacao OBJECT-TYPE
    SYNTAX      Integer32
    MAX-ACCESS  read-only
    STATUS      current
    DESCRIPTION
            "Description"
    ::= { redeSegurancaObjectEntry 13 }

paginaPadraoHttp OBJECT-TYPE
    SYNTAX      DisplayString
    MAX-ACCESS  read-only
    STATUS      current
    DESCRIPTION
            "Description"
    ::= { redeSegurancaObjectEntry 14 }

emailServerEntry OBJECT-IDENTITY
    STATUS  current
    DESCRIPTION
            "EmailServer table"
    ::= { settingsObject 5 }

server OBJECT-TYPE
    SYNTAX      DisplayString
    MAX-ACCESS  read-only
    STATUS      current
    DESCRIPTION
            "Description"
    ::= { emailServerEntry 1 }

portaSMTP OBJECT-TYPE
    SYNTAX      Integer32
    MAX-ACCESS  read-only
    STATUS      current
    DESCRIPTION
            "Description"
    ::= { emailServerEntry 2 }

usarCriptografiaTLS OBJECT-TYPE
    SYNTAX      Integer32
    MAX-ACCESS  read-only
    STATUS      current
    DESCRIPTION
            "Description"
    ::= { emailServerEntry 3 }

emailAdmin OBJECT-TYPE
    SYNTAX      DisplayString
    MAX-ACCESS  read-only
    STATUS      current
    DESCRIPTION
            "Description"
    ::= { emailServerEntry 4 }

assunto OBJECT-TYPE
    SYNTAX      DisplayString
    MAX-ACCESS  read-only
    STATUS      current
    DESCRIPTION
            "Description"
    ::= { emailServerEntry 5 }

usarAutenticacao OBJECT-TYPE
    SYNTAX      DisplayString
    MAX-ACCESS  read-only
    STATUS      current
    DESCRIPTION
            "Description"
    ::= { emailServerEntry 6 }

login OBJECT-TYPE
    SYNTAX      DisplayString
    MAX-ACCESS  read-only
    STATUS      current
    DESCRIPTION
            "Description"
    ::= { emailServerEntry 7 }

timeServerEntry OBJECT-IDENTITY
    STATUS  current
    DESCRIPTION
            "TimeServer table"
    ::= { settingsObject 6 }

timeServerAddress1 OBJECT-TYPE
    SYNTAX      DisplayString
    MAX-ACCESS  read-only
    STATUS      current
    DESCRIPTION
            "Description"
    ::= { timeServerEntry 1 }

timeServerAddress1Complemento OBJECT-TYPE
    SYNTAX      DisplayString
    MAX-ACCESS  read-only
    STATUS      current
    DESCRIPTION
            "Description"
    ::= { timeServerEntry 2 }

timeServerAddress2 OBJECT-TYPE
    SYNTAX      DisplayString
    MAX-ACCESS  read-only
    STATUS      current
    DESCRIPTION
            "Description"
    ::= { timeServerEntry 3 }

timeServerAddress2Complemento OBJECT-TYPE
    SYNTAX      DisplayString
    MAX-ACCESS  read-only
    STATUS      current
    DESCRIPTION
            "Description"
    ::= { timeServerEntry 4 }

timeServerAddress3 OBJECT-TYPE
    SYNTAX      DisplayString
    MAX-ACCESS  read-only
    STATUS      current
    DESCRIPTION
            "Description"
    ::= { timeServerEntry 5 }

timeServerAddress3Complemento OBJECT-TYPE
    SYNTAX      DisplayString
    MAX-ACCESS  read-only
    STATUS      current
    DESCRIPTION
            "Description"
    ::= { timeServerEntry 6 }

connectionRetries OBJECT-TYPE
    SYNTAX      Integer32
    MAX-ACCESS  read-only
    STATUS      current
    DESCRIPTION
            "Description"
    ::= { timeServerEntry 7 }

timeZone OBJECT-TYPE
    SYNTAX      DisplayString
    MAX-ACCESS  read-only
    STATUS      current
    DESCRIPTION
            "Description"
    ::= { timeServerEntry 8 }

automAdjustLightSaving OBJECT-TYPE
    SYNTAX      DisplayString
    MAX-ACCESS  read-only
    STATUS      current
    DESCRIPTION
            "Description"
    ::= { timeServerEntry 9 }

alarmeConfigEntry OBJECT-IDENTITY
    STATUS  current
    DESCRIPTION
            "AlarmeConfig table"
    ::= { settingsObject 7 }

tipoModulo OBJECT-TYPE
    SYNTAX      DisplayString
    MAX-ACCESS  read-only
    STATUS      current
    DESCRIPTION
            "Description"
    ::= { alarmeConfigEntry 1 }

nivelAlertTensaoMax OBJECT-TYPE
    SYNTAX      DisplayString
    MAX-ACCESS  read-only
    STATUS      current
    DESCRIPTION
            "Description"
    ::= { alarmeConfigEntry 2 }

nivelAlertTensaoMin OBJECT-TYPE
    SYNTAX      DisplayString
    MAX-ACCESS  read-only
    STATUS      current
    DESCRIPTION
            "Description"
    ::= { alarmeConfigEntry 3 }

nivelAlertTempMax OBJECT-TYPE
    SYNTAX      DisplayString
    MAX-ACCESS  read-only
    STATUS      current
    DESCRIPTION
            "Description"
    ::= { alarmeConfigEntry 4 }

nivelAlertTempMin OBJECT-TYPE
    SYNTAX      DisplayString
    MAX-ACCESS  read-only
    STATUS      current
    DESCRIPTION
            "Description"
    ::= { alarmeConfigEntry 5 }

nivelAlertImpedanciaMax OBJECT-TYPE
    SYNTAX      DisplayString
    MAX-ACCESS  read-only
    STATUS      current
    DESCRIPTION
            "Description"
    ::= { alarmeConfigEntry 6 }

nivelAlertImpedanciaMin OBJECT-TYPE
    SYNTAX      DisplayString
    MAX-ACCESS  read-only
    STATUS      current
    DESCRIPTION
            "Description"
    ::= { alarmeConfigEntry 7 }

nivelMaxTensaoAtivo OBJECT-TYPE
    SYNTAX      DisplayString
    MAX-ACCESS  read-only
    STATUS      current
    DESCRIPTION
            "Description"
    ::= { alarmeConfigEntry 8 }

nivelMaxTensaoVal OBJECT-TYPE
    SYNTAX      DisplayString
    MAX-ACCESS  read-only
    STATUS      current
    DESCRIPTION
            "Description"
    ::= { alarmeConfigEntry 9 }

alarmeNivelTensaoMax OBJECT-TYPE
    SYNTAX      DisplayString
    MAX-ACCESS  read-only
    STATUS      current
    DESCRIPTION
            "Description"
    ::= { alarmeConfigEntry 10 }

alarmeNivelTensaoMin OBJECT-TYPE
    SYNTAX      DisplayString
    MAX-ACCESS  read-only
    STATUS      current
    DESCRIPTION
            "Description"
    ::= { alarmeConfigEntry 11 }

alarmeNivelTempMax OBJECT-TYPE
    SYNTAX      DisplayString
    MAX-ACCESS  read-only
    STATUS      current
    DESCRIPTION
            "Description"
    ::= { alarmeConfigEntry 12 }

alarmeNivelTempMin OBJECT-TYPE
    SYNTAX      DisplayString
    MAX-ACCESS  read-only
    STATUS      current
    DESCRIPTION
            "Description"
    ::= { alarmeConfigEntry 13 }

alarmeNivelImpedMax OBJECT-TYPE
    SYNTAX      DisplayString
    MAX-ACCESS  read-only
    STATUS      current
    DESCRIPTION
            "Description"
    ::= { alarmeConfigEntry 14 }

alarmeNivelImpedMin OBJECT-TYPE
    SYNTAX      DisplayString
    MAX-ACCESS  read-only
    STATUS      current
    DESCRIPTION
            "Description"
    ::= { alarmeConfigEntry 15 }

alarmeNivelTensaoBarrMin OBJECT-TYPE
    SYNTAX      DisplayString
    MAX-ACCESS  read-only
    STATUS      current
    DESCRIPTION
            "Description"
    ::= { alarmeConfigEntry 16 }

alarmeNivelTensaoBarrMax OBJECT-TYPE
    SYNTAX      DisplayString
    MAX-ACCESS  read-only
    STATUS      current
    DESCRIPTION
            "Description"
    ::= { alarmeConfigEntry 17 }

alarmeNivelTargetMin OBJECT-TYPE
    SYNTAX      DisplayString
    MAX-ACCESS  read-only
    STATUS      current
    DESCRIPTION
            "Description"
    ::= { alarmeConfigEntry 18 }

alarmeNivelTargetMax OBJECT-TYPE
    SYNTAX      DisplayString
    MAX-ACCESS  read-only
    STATUS      current
    DESCRIPTION
            "Description"
    ::= { alarmeConfigEntry 19 }

apelidoStringEntry OBJECT-IDENTITY
    STATUS  current
    DESCRIPTION
            "ApelidoString table"
    ::= { settingsObject 8 }

apString OBJECT-TYPE
    SYNTAX      DisplayString
    MAX-ACCESS  read-only
    STATUS      current
    DESCRIPTION
            "Description"
    ::= { apelidoStringEntry 1 }

apelido OBJECT-TYPE
    SYNTAX      DisplayString
    MAX-ACCESS  read-only
    STATUS      current
    DESCRIPTION
            "Description"
    ::= { apelidoStringEntry 2 }

bateriaObject OBJECT-IDENTITY
    STATUS  current
    DESCRIPTION
            "Bateria object"
    ::= { equalizer 2 }

bateriaTable OBJECT-TYPE
    SYNTAX     SEQUENCE OF BateriaEntry
    MAX-ACCESS not-accessible
    STATUS     current
    DESCRIPTION
            "Tabela com as baterias do modulo"
    ::= { bateriaObject 1 }

bateriaEntry OBJECT-TYPE
    SYNTAX     BateriaEntry
    MAX-ACCESS not-accessible
    STATUS     current
    DESCRIPTION
            "An entry (conceptual row) in the sysORTable."
    INDEX      { bateriaIndex }
    ::= { bateriaTable 1 }

BateriaEntry ::= SEQUENCE {
    bateriaIndex  Integer32,
    string     DisplayString,
    bateria     DisplayString,
    tensao        DisplayString,
    temperatura     DisplayString,
    impedancia    DisplayString,
    equalizacao   DisplayString
}

bateriaIndex OBJECT-TYPE
    SYNTAX     Integer32(1..256)
    MAX-ACCESS not-accessible
    STATUS     current
    DESCRIPTION
            "Indice da tabela, corresponde ao ID do BD."
    ::= { bateriaEntry 1 }

string OBJECT-TYPE
    SYNTAX     DisplayString
    MAX-ACCESS read-only
    STATUS     current
    DESCRIPTION
            "Identificador do banco."
    ::= { bateriaEntry 2 }

bateria OBJECT-TYPE
    SYNTAX     DisplayString
    MAX-ACCESS read-only
    STATUS     current
    DESCRIPTION
            "Identificador da bateria no banco."
    ::= { bateriaEntry 3 }

tensao OBJECT-TYPE
    SYNTAX     DisplayString
    MAX-ACCESS read-only
    STATUS     current
    DESCRIPTION
            "Tensao da bateria."
    ::= { bateriaEntry 4 }

temperatura OBJECT-TYPE
    SYNTAX     DisplayString
    MAX-ACCESS read-only
    STATUS     current
    DESCRIPTION
            "Temperatura da bateria."
    ::= { bateriaEntry 5 }

impedancia OBJECT-TYPE
    SYNTAX     DisplayString
    MAX-ACCESS read-only
    STATUS     current
    DESCRIPTION
            "Impedancia da bateria."
    ::= { bateriaEntry 6 }

equalizacao OBJECT-TYPE
    SYNTAX     DisplayString
    MAX-ACCESS read-only
    STATUS     current
    DESCRIPTION
            "Equalizacao da bateria."
    ::= { bateriaEntry 7 }

tensaoBarr OBJECT-TYPE
    SYNTAX     DisplayString
    MAX-ACCESS read-only
    STATUS     current
    DESCRIPTION
            "Tensao de barramento."
    ::= { bateriaObject 2 }

target OBJECT-TYPE
    SYNTAX     DisplayString
    MAX-ACCESS read-only
    STATUS     current
    DESCRIPTION
            "Target de tensao."
    ::= { bateriaObject 3 }

bateriaLogTable OBJECT-TYPE
    SYNTAX     SEQUENCE OF BateriaLogEntry
    MAX-ACCESS not-accessible
    STATUS     current
    DESCRIPTION
            "Tabela com os dados historicos de baterias do modulo"
    ::= { bateriaObject 4 }

bateriaLogEntry OBJECT-TYPE
    SYNTAX     BateriaLogEntry
    MAX-ACCESS not-accessible
    STATUS     current
    DESCRIPTION
            "An entry (conceptual row) in the sysORTable."
    INDEX      { bateriaLogIndex }
    ::= { bateriaLogTable 1 }

BateriaLogEntry ::= SEQUENCE {
    bateriaLogIndex  Integer32,
    stringLog     DisplayString,
    bateriaLog     DisplayString,
    tensaoLog        DisplayString,
    temperaturaLog     DisplayString,
    impedanciaLog    DisplayString,
    equalizacaoLog   DisplayString
}

bateriaLogIndex OBJECT-TYPE
    SYNTAX     Integer32(1..256)
    MAX-ACCESS not-accessible
    STATUS     current
    DESCRIPTION
            "Indice da tabela, corresponde ao ID do BD."
    ::= { bateriaLogEntry 1 }

stringLog OBJECT-TYPE
    SYNTAX     DisplayString
    MAX-ACCESS read-only
    STATUS     current
    DESCRIPTION
            "Identificador do banco."
    ::= { bateriaLogEntry 2 }

bateriaLog OBJECT-TYPE
    SYNTAX     DisplayString
    MAX-ACCESS read-only
    STATUS     current
    DESCRIPTION
            "Identificador da bateria no banco."
    ::= { bateriaLogEntry 3 }

tensaoLog OBJECT-TYPE
    SYNTAX     DisplayString
    MAX-ACCESS read-only
    STATUS     current
    DESCRIPTION
            "Tensao da bateria."
    ::= { bateriaLogEntry 4 }

temperaturaLog OBJECT-TYPE
    SYNTAX     DisplayString
    MAX-ACCESS read-only
    STATUS     current
    DESCRIPTION
            "Temperatura da bateria."
    ::= { bateriaLogEntry 5 }

impedanciaLog OBJECT-TYPE
    SYNTAX     DisplayString
    MAX-ACCESS read-only
    STATUS     current
    DESCRIPTION
            "Impedancia da bateria."
    ::= { bateriaLogEntry 6 }

equalizacaoLog OBJECT-TYPE
    SYNTAX     DisplayString
    MAX-ACCESS read-only
    STATUS     current
    DESCRIPTION
            "Equalizacao da bateria."
    ::= { bateriaLogEntry 7 }

alarmeObject OBJECT-IDENTITY
    STATUS  current
    DESCRIPTION
            "Alarme object"
    ::= { equalizer 3 }

alarmeTable OBJECT-TYPE
    SYNTAX     SEQUENCE OF AlarmeEntry
    MAX-ACCESS not-accessible
    STATUS     current
    DESCRIPTION
            "Tabela com os alarmes do modulo"
    ::= { alarmeObject 1 }

alarmeEntry OBJECT-TYPE
    SYNTAX     AlarmeEntry
    MAX-ACCESS not-accessible
    STATUS     current
    DESCRIPTION
            "Alarm entry."
    INDEX      { alarmeIndex }
    ::= { alarmeTable 1 }

AlarmeEntry ::= SEQUENCE {
    alarmeIndex  Integer32,
    descricaoAlarm     Integer32,
    emailEnviado     DisplayString,
    nOcorrencias        DisplayString
}

alarmeIndex OBJECT-TYPE
    SYNTAX     Integer32(1..256)
    MAX-ACCESS not-accessible
    STATUS     current
    DESCRIPTION
            "Indice da tabela, corresponde ao ID do BD."
    ::= { alarmeEntry 1 }

descricaoAlarm OBJECT-TYPE
    SYNTAX     Integer32
    MAX-ACCESS read-only
    STATUS     current
    DESCRIPTION
            "Descricao"
    ::= { alarmeEntry 2 }

emailEnviado OBJECT-TYPE
    SYNTAX     DisplayString
    MAX-ACCESS read-only
    STATUS     current
    DESCRIPTION
            "Descricao"
    ::= { alarmeEntry 3 }

nOcorrencias OBJECT-TYPE
    SYNTAX     DisplayString
    MAX-ACCESS read-only
    STATUS     current
    DESCRIPTION
            "Descricao"
    ::= { alarmeEntry 4 }

---
--- equalizerConformance
---

equalizerCompliance
               OBJECT IDENTIFIER ::= { equalizer 4 }
equalizerGroups
               OBJECT IDENTIFIER ::= { equalizer 5 }

equalizerComplianceRev1 MODULE-COMPLIANCE
    STATUS  current
    DESCRIPTION
            "The compliance statement for SNMP entities which
            implement this MIB module."
    MODULE  -- this module
        MANDATORY-GROUPS { parameterGroup,
                  moduloGroup,
                  usuariosGroup,
                  redeSegurancaGroup,
                  bateriasGroup,
                  emailServerGroup,
                  timeServerGroup,
                  alarmeConfigGroup,
                  apelidoStringGroup,
                  alarmeGroup
                }
    ::= { equalizerCompliance 1 }

parameterGroup OBJECT-GROUP
    OBJECTS {
      avgLast,
      dutyMin,
      dutyMax,
      cteIndex,
      delay,
      numCyclesVarRead,
      busVoltage,
      saveLogTime,
      diskCapacity,
      param1,
      param2,
      param3,
      param4,
      param5,
      param6,
      param7,
      param8,
      param9,
      param10
    }
    STATUS  current
    DESCRIPTION
            "Basic parameters group."
    ::= { equalizerGroups 1 }

moduloGroup OBJECT-GROUP
    OBJECTS {
      descricao,
      tensaoNominal,
      capacidadeNominal,
      nStrings,
      nBateriasPorStrings,
      contato,
      localizacao,
      fabricante,
      tipo,
      dataInstalacao,
      confAlarmeId
     }
    STATUS  current
    DESCRIPTION
            "Basic modulo group."
    ::= { equalizerGroups 2 }

usuariosGroup OBJECT-GROUP
    OBJECTS {
      nome,
      sobreNome,
      telefone,
      email,
      senha,
      acesso
    }
    STATUS  current
    DESCRIPTION
            "Basic usuarios group."
    ::= { equalizerGroups 3 }

redeSegurancaGroup OBJECT-GROUP
    OBJECTS {
      mac,
      velocidadePlacaRede,
      localAddress,
      gateway,
      mascara,
      servidorDNS,
      nomeDoSistema,
      localDoSistema,
      contatoDoSistema,
      httpPort,
      useHttps,
      httpsPort,
      httpTempoDeAtualizacao,
      paginaPadraoHttp
    }
    STATUS  current
    DESCRIPTION
            "Basic RedeSeguranca group."
    ::= { equalizerGroups 4 }

bateriasGroup OBJECT-GROUP
    OBJECTS {
      string,
      bateria,
      tensao,
      temperatura,
      impedancia,
      equalizacao,
      tensaoBarr,
      target,
      stringLog,
      bateriaLog,
      tensaoLog,
      temperaturaLog,
      impedanciaLog,
      equalizacaoLog
    }
    STATUS  current
    DESCRIPTION
            "Baterias group."
    ::= { equalizerGroups 5 }

emailServerGroup OBJECT-GROUP
    OBJECTS {
      server,
      portaSMTP,
      usarCriptografiaTLS,
      emailAdmin,
      assunto,
      usarAutenticacao,
      login
    }
    STATUS  current
    DESCRIPTION
          "EmailServer group."
    ::= { equalizerGroups 6 }

timeServerGroup OBJECT-GROUP
    OBJECTS {
      timeServerAddress1,
      timeServerAddress1Complemento,
      timeServerAddress2,
      timeServerAddress2Complemento,
      timeServerAddress3,
      timeServerAddress3Complemento,
      connectionRetries,
      timeZone,
      automAdjustLightSaving
    }
    STATUS  current
    DESCRIPTION
          "TimeServer group."
    ::= { equalizerGroups 7 }

alarmeConfigGroup OBJECT-GROUP
    OBJECTS {
      tipoModulo,
      nivelAlertTensaoMax,
      nivelAlertTensaoMin,
      nivelAlertTempMax,
      nivelAlertTempMin,
      nivelAlertImpedanciaMax,
      nivelAlertImpedanciaMin,
      nivelMaxTensaoAtivo,
      nivelMaxTensaoVal,
      alarmeNivelTensaoMax,
      alarmeNivelTensaoMin,
      alarmeNivelTempMax,
      alarmeNivelTempMin,
      alarmeNivelImpedMax,
      alarmeNivelImpedMin,
      alarmeNivelTensaoBarrMin,
      alarmeNivelTensaoBarrMax,
      alarmeNivelTargetMin,
      alarmeNivelTargetMax
    }
    STATUS  current
    DESCRIPTION
          "AlarmeConfig group."
    ::= { equalizerGroups 8 }

apelidoStringGroup OBJECT-GROUP
    OBJECTS {
      apString,
      apelido
    }
    STATUS  current
    DESCRIPTION
          "ApelidoString group."
    ::= { equalizerGroups 9 }

alarmeGroup OBJECT-GROUP
    OBJECTS {
      descricaoAlarm,
      emailEnviado,
      nOcorrencias
    }
    STATUS  current
    DESCRIPTION
          "AlarmeLog group."
    ::= { equalizerGroups 10 }


END
